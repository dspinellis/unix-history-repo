-- smux.my - SMUX management objects

-- $Header: /f/osi/snmp/RCS/smux.my,v 7.13 91/02/28 17:17:21 mrose Exp $
--
-- Contributed by NYSERNet Inc.  This work was partially supported by the
-- U.S. Defense Advanced Research Projects Agency and the Rome Air Development
-- Center of the U.S. Air Force Systems Command under contract number
-- F30602-88-C-0016.
--
--
-- $Log:	smux.my,v $
-- Revision 7.13  91/02/28  17:17:21  mrose
-- touch-up
-- 
-- Revision 7.12  91/02/22  09:44:02  mrose
-- Interim 6.8
-- 
-- Revision 7.11  91/01/11  14:13:47  mrose
-- update
-- 
-- Revision 7.10  90/06/23  01:33:01  mrose
-- touch-up
-- 
-- Revision 7.9  90/05/31  10:38:35  mrose
-- update
-- 
-- Revision 7.8  90/05/28  21:50:06  mrose
-- not-accessible
-- 
-- Revision 7.7  90/05/21  17:07:25  mrose
-- OBJECT-TYPE
-- 
-- Revision 7.6  90/05/13  15:54:35  mrose
-- update
-- 
-- Revision 7.5  90/04/17  01:02:35  mrose
-- update
-- 
-- Revision 7.4  90/03/24  10:53:33  mrose
-- touch-up
-- 
-- Revision 7.3  90/03/24  10:53:08  mrose
-- touch-up
-- 
-- Revision 7.2  90/03/24  10:50:19  mrose
-- touch-up
-- 
-- Revision 7.1  90/02/27  18:49:52  mrose
-- unix stuff
-- 
-- Revision 7.0  90/02/19  10:43:54  mrose
-- *** empty log message ***
-- 

--
--				  NOTICE
--
--    Acquisition, use, and distribution of this module and related
--    materials are subject to the restrictions of a license agreement.
--    Consult the Preface in the User's Manual for the full terms of
--    this agreement.
--
--


SMUX-MIB DEFINITIONS ::= BEGIN

IMPORTS
	unix, OBJECT-TYPE, Counter, ObjectName
		FROM RFC1155-SMI;


-- the SMUX protocol group

smux	OBJECT IDENTIFIER ::= { unix 4 }

smuxPeerTable	OBJECT-TYPE
	SYNTAX	SEQUENCE OF SmuxPeerEntry
	ACCESS	not-accessible
	STATUS	mandatory
	::= { smux 1 }

smuxPeerEntry	OBJECT-TYPE
	SYNTAX	SmuxPeerEntry
	ACCESS	not-accessible
	STATUS	mandatory
  	INDEX	{ smuxPindex }
	::= { smuxPeerTable 1}

SmuxPeerEntry ::= SEQUENCE {
    smuxPindex
	INTEGER,
    smuxPidentity
	OBJECT IDENTIFIER,
    smuxPdescription
	DisplayString,
    smuxPstatus
	INTEGER
}

smuxPindex	OBJECT-TYPE
	SYNTAX	INTEGER
	ACCESS	read-only
	STATUS	mandatory
	::= { smuxPeerEntry 1 }

smuxPidentity	OBJECT-TYPE
	SYNTAX	OBJECT IDENTIFIER
	ACCESS	read-only
	STATUS	mandatory
	::= { smuxPeerEntry 2 }

smuxPdescription OBJECT-TYPE
	SYNTAX	DisplayString (SIZE (0..255))
	ACCESS	read-only
	STATUS	mandatory
	::= { smuxPeerEntry 3 }

smuxPstatus	OBJECT-TYPE
	SYNTAX	INTEGER { valid(1), invalid(2), connecting(3) }
	ACCESS	read-write
	STATUS	mandatory
	::= { smuxPeerEntry 4 }

smuxTreeTable	OBJECT-TYPE
	SYNTAX	SEQUENCE OF SmuxTreeEntry
	ACCESS	not-accessible
	STATUS	mandatory
	::= { smux 2 }

smuxTreeEntry	OBJECT-TYPE
	SYNTAX	SmuxTreeEntry
	ACCESS	not-accessible
	STATUS	mandatory
  	INDEX	{ smuxTsubtree, smuxTpriority }
	::= { smuxTreeTable 1}

SmuxTreeEntry ::= SEQUENCE {
    smuxTsubtree
	--* ObjectName *-- OBJECT IDENTIFIER,
    smuxTpriority
	INTEGER,
    smuxTindex
	INTEGER,
    smuxTstatus
	INTEGER
}

smuxTsubtree	OBJECT-TYPE
	SYNTAX	--* ObjectName *-- OBJECT IDENTIFIER
	ACCESS	read-only
	STATUS	mandatory
	::= { smuxTreeEntry 1 }

smuxTpriority OBJECT-TYPE
	SYNTAX	INTEGER (0..2147483647)
	ACCESS	read-only
	STATUS	mandatory
	::= { smuxTreeEntry 2 }

smuxTindex OBJECT-TYPE
	SYNTAX	INTEGER (0..2147483647)
	ACCESS	read-only
	STATUS	mandatory
	::= { smuxTreeEntry 3 }

smuxTstatus	OBJECT-TYPE
	SYNTAX	INTEGER { valid(1), invalid(2) }
	ACCESS	read-write
	STATUS	mandatory
	::= { smuxTreeEntry 4 }


-- the NETSTAT group

netstat	OBJECT IDENTIFIER ::=	{ unix 5 }

unixNetstat	OBJECT-TYPE
	SYNTAX	INTEGER { enabled(1), disabled(2) }
	ACCESS	read-only
	STATUS	mandatory
	::= { netstat 1 }

-- the UNIX TCP connections table

unixTcpConnTable OBJECT-TYPE
	SYNTAX	SEQUENCE OF UnixTcpConnEntry
	ACCESS	not-accessible
	STATUS	mandatory
	::= { netstat 2 }

unixTcpConnEntry OBJECT-TYPE
	SYNTAX	UnixTcpConnEntry
	ACCESS	not-accessible
	STATUS	mandatory
  	INDEX	{ tcpConnLocalAddress, tcpConnLocalPort, tcpConnRemAddress, tcpConnRemPort }
	::= { unixTcpConnTable 1 }

UnixTcpConnEntry ::= SEQUENCE {
    unixTcpConnSendQ
	INTEGER,
    unixTcpConnRecvQ
	INTEGER
}

unixTcpConnSendQ OBJECT-TYPE
	SYNTAX	INTEGER
	ACCESS	read-only
	STATUS	mandatory
	::= { unixTcpConnEntry 1 }

unixTcpConnRecvQ OBJECT-TYPE
	SYNTAX	INTEGER
	ACCESS	read-only
	STATUS	mandatory
	::= { unixTcpConnEntry 2 }


-- the UNIX UDP listener table

unixUdpTable OBJECT-TYPE
	SYNTAX	SEQUENCE OF UnixUdpEntry
	ACCESS	not-accessible
	STATUS	mandatory
	::= { netstat 3 }

unixUdpEntry OBJECT-TYPE
	SYNTAX	UnixUdpEntry
	ACCESS	not-accessible
	STATUS	mandatory
  	INDEX	{ udpLocalAddress, udpLocalPort }
	::= { unixUdpTable 1 }

UnixUdpEntry ::= SEQUENCE {
    unixUdpRemAddress
	IpAddress,
    unixUdpRemPort
	INTEGER (0..65535),
    unixUdpSendQ
	INTEGER,
    unixUdpRecvQ
	INTEGER
}

unixUdpRemAddress OBJECT-TYPE
	SYNTAX	IpAddress
	ACCESS	read-only
	STATUS	mandatory
	::= { unixUdpEntry 1 }

unixUdpRemPort OBJECT-TYPE
	SYNTAX	INTEGER (0..65535)
	ACCESS	read-only
	STATUS	mandatory
	::= { unixUdpEntry 2 }

unixUdpSendQ OBJECT-TYPE
	SYNTAX	INTEGER
	ACCESS	read-only
	STATUS	mandatory
	::= { unixUdpEntry 3 }

unixUdpRecvQ OBJECT-TYPE
	SYNTAX	INTEGER
	ACCESS	read-only
	STATUS	mandatory
	::= { unixUdpEntry 4 }

-- the UNIX IP Routing table

unixIpRoutingTable OBJECT-TYPE
	SYNTAX	SEQUENCE OF UnixIpRouteEntry
	ACCESS	not-accessible
	STATUS	mandatory
	::= { netstat 4 }

unixIpRouteEntry OBJECT-TYPE
	SYNTAX	UnixIpRouteEntry
	ACCESS	not-accessible
	STATUS	mandatory
  	INDEX	{ ipRouteDest }
	::= { unixIpRoutingTable 1 }

UnixIpRouteEntry ::= SEQUENCE {
    unixIpRouteFlags
	INTEGER,
    unixIpRouteRefCnt
	INTEGER,
    unixIpRouteUses
	Counter
}

unixIpRouteFlags OBJECT-TYPE
	SYNTAX	INTEGER
	ACCESS	read-only
	STATUS	mandatory
	::= { unixIpRouteEntry 1 }

unixIpRouteRefCnt OBJECT-TYPE
	SYNTAX	INTEGER
	ACCESS	read-only
	STATUS	mandatory
	::= { unixIpRouteEntry 2 }

unixIpRouteUses OBJECT-TYPE
	SYNTAX	Counter
	ACCESS	read-only
	STATUS	mandatory
	::= { unixIpRouteEntry 3 }

-- miscellaneous UNIX routing statistics

unixRouteBadRedirects	OBJECT-TYPE
	SYNTAX	Counter
	ACCESS	read-only
	STATUS	mandatory
	::= { netstat 5 }

unixRouteCreatedByRedirects OBJECT-TYPE
	SYNTAX	Counter
	ACCESS	read-only
	STATUS	mandatory
	::= { netstat 6 }

unixRouteModifiedByRedirects OBJECT-TYPE
	SYNTAX	Counter
	ACCESS	read-only
	STATUS	mandatory
	::= { netstat 7 }

unixRouteLookupFails	OBJECT-TYPE
	SYNTAX	Counter
	ACCESS	read-only
	STATUS	mandatory
	::= { netstat 8 }

unixRouteWildcardUses	OBJECT-TYPE
	SYNTAX	Counter
	ACCESS	read-only
	STATUS	mandatory
	::= { netstat 9 }

-- the UNIX CLNP Routing table

unixClnpRoutingTable OBJECT-TYPE
	SYNTAX	SEQUENCE OF UnixClnpRouteEntry
	ACCESS	not-accessible
	STATUS	mandatory
	::= { netstat 10 }

unixClnpRouteEntry OBJECT-TYPE
	SYNTAX	UnixClnpRouteEntry
	ACCESS	not-accessible
	STATUS	mandatory
  	INDEX	{ clnpRouteDest }
	::= { unixClnpRoutingTable 1 }

UnixClnpRouteEntry ::= SEQUENCE {
    unixClnpRouteFlags
	INTEGER,
    unixClnpRouteRefCnt
	INTEGER,
    unixClnpRouteUses
	Counter
}

unixClnpRouteFlags OBJECT-TYPE
	SYNTAX	INTEGER
	ACCESS	read-only
	STATUS	mandatory
	::= { unixClnpRouteEntry 1 }

unixClnpRouteRefCnt OBJECT-TYPE
	SYNTAX	INTEGER
	ACCESS	read-only
	STATUS	mandatory
	::= { unixClnpRouteEntry 2 }

unixClnpRouteUses OBJECT-TYPE
	SYNTAX	Counter
	ACCESS	read-only
	STATUS	mandatory
	::= { unixClnpRouteEntry 3 }

END
