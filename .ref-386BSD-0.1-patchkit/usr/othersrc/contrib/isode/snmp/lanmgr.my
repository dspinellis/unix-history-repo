-- lanmgr.my - LANmanager version 1 MIB

-- $Header: /f/osi/snmp/RCS/lanmgr.my,v 7.2 91/02/22 09:43:30 mrose Interim $
--
-- 
-- $Log:	lanmgr.my,v $
-- Revision 7.2  91/02/22  09:43:30  mrose
-- Interim 6.8
-- 
-- Revision 7.1  90/09/26  19:28:14  mrose
-- typo
-- 
-- Revision 7.0  90/09/26  19:21:23  mrose
-- *** empty log message ***
-- 

--
--				  NOTICE
--
--    Acquisition, use, and distribution of this module and related
--    materials are subject to the restrictions of a license agreement.
--    Consult the Preface in the User's Manual for the full terms of
--    this agreement.
--
--


          RFCxxxx-MIB DEFINITIONS ::= BEGIN

               IMPORTS
                    experimental, OBJECT-TYPE, Counter FROM RFC1155-SMI;

               lanmgr-1    OBJECT IDENTIFIER ::= { experimental 9 }

               common         OBJECT IDENTIFIER ::= { lanmgr-1 1 }
               server         OBJECT IDENTIFIER ::= { lanmgr-1 2 }
               workstation    OBJECT IDENTIFIER ::= { lanmgr-1 3 }


               -- object types

               -- the common group

               comVersionMaj OBJECT-TYPE
                       SYNTAX INTEGER
                       ACCESS read-only
                       STATUS mandatory
                       ::= { common 1 }


               comVersionMin OBJECT-TYPE
                       SYNTAX INTEGER
                       ACCESS read-only
                       STATUS mandatory
                       ::= { common 2 }


               comType OBJECT-TYPE
                       SYNTAX OCTET STRING (SIZE (4))
                       ACCESS read-only
                       STATUS mandatory
                       ::= { common 3 }


               comStatStart OBJECT-TYPE
                       SYNTAX INTEGER
                       ACCESS read-only
                       STATUS mandatory
                       ::= { common 4 }







               comStatNumNetIOs OBJECT-TYPE
                       SYNTAX Counter
                       ACCESS read-only
                       STATUS mandatory
                       ::= { common 5 }


               comStatFiNetIOs OBJECT-TYPE
                       SYNTAX Counter
                       ACCESS read-only
                       STATUS mandatory
                       ::= { common 6 }


               comStatFcNetIOs OBJECT-TYPE
                       SYNTAX Counter
                       ACCESS read-only
                       STATUS mandatory
                       ::= { common 7 }


               -- the Server group

               svDescription OBJECT-TYPE
                       SYNTAX DisplayString (SIZE (0..255))
                       ACCESS read-only
                       STATUS mandatory
                       ::= { server 1 }


               svSvcNumber OBJECT-TYPE
                       SYNTAX INTEGER
                       ACCESS read-only
                       STATUS mandatory
                       ::= { server 2 }


               -- the Services table

               svSvcTable OBJECT-TYPE
                       SYNTAX SEQUENCE OF SvSvcEntry
                       ACCESS not-accessible
                       STATUS mandatory
                       ::= { server 3 }







               svSvcEntry OBJECT-TYPE
                       SYNTAX SvSvcEntry
                       ACCESS not-accessible
                       STATUS mandatory
                       ::= { svSvcTable 1 }


               SvSvcEntry ::= SEQUENCE {
                       svSvcName
                           DisplayString (SIZE (0..255)),
                       svSvcInstalledState
                           INTEGER,
                       svSvcOperatingState
                           INTEGER,
                       svSvcCanBeUnInstalled
                           INTEGER,
                       svSvcCanBePaused
                           INTEGER
                       }


               svSvcName OBJECT-TYPE
                       SYNTAX DisplayString (SIZE(0..255))
                       ACCESS read-only
                       STATUS mandatory
                       ::= { svSvcEntry 1 }


               svSvcInstalledState OBJECT-TYPE
                       SYNTAX INTEGER {
                         uninstalled(1),
                         install-pending(2),
                         uninstall-pending(3),
                         installed(4)
                         }
                       ACCESS read-only
                       STATUS mandatory
                       ::= { svSvcEntry 2 }


               svSvcOperatingState OBJECT-TYPE
                       SYNTAX INTEGER {
                         active(1),
                         continue-pending(2),
                         pause-pending(3),






                         paused(4)
                         }
                       ACCESS read-only
                       STATUS mandatory
                       ::= { svSvcEntry 3 }


               svSvcCanBeUninstalled OBJECT-TYPE
                       SYNTAX INTEGER {
                         cannot-be-uninstalled(1),
                         can-be-uninstalled(2)
                         }
                       ACCESS read-only
                       STATUS mandatory
                       ::= { svSvcEntry 4 }


               svSvcCanBePaused OBJECT-TYPE
                       SYNTAX INTEGER {
                         cannot-be-paused(1),
                         can-be-paused(2)
                         }
                       ACCESS read-only
                       STATUS mandatory
                       ::= { svSvcEntry 5 }


               svStatOpens OBJECT-TYPE
                       SYNTAX Counter
                       ACCESS read-only
                       STATUS mandatory
                       ::= { server 4 }


               svStatDevOpens OBJECT-TYPE
                       SYNTAX Counter
                       ACCESS read-only
                       STATUS mandatory
                       ::= { server 5 }


               svStatQueuedJobs OBJECT-TYPE
                       SYNTAX Counter
                       ACCESS read-only
                       STATUS mandatory






                       ::= { server 6 }


               svStatSOpens OBJECT-TYPE
                       SYNTAX Counter
                       ACCESS read-only
                       STATUS mandatory
                       ::= { server 7 }


               svStatErrorOuts OBJECT-TYPE
                       SYNTAX Counter
                       ACCESS read-only
                       STATUS mandatory
                       ::= { server 8 }


               svStatPwErrors OBJECT-TYPE
                       SYNTAX Counter
                       ACCESS read-only
                       STATUS mandatory
                       ::= { server 9 }


               svStatPermErrors OBJECT-TYPE
                       SYNTAX Counter
                       ACCESS read-only
                       STATUS mandatory
                       ::= { server 10 }


               svStatSysErrors OBJECT-TYPE
                       SYNTAX Counter
                       ACCESS read-only
                       STATUS mandatory
                       ::= { server 11 }


               svStatSentBytes OBJECT-TYPE
                       SYNTAX Counter
                       ACCESS read-only
                       STATUS mandatory
                       ::= { server 12 }








               svStatRcvdBytes OBJECT-TYPE
                       SYNTAX Counter
                       ACCESS read-only
                       STATUS mandatory
                       ::= { server 13 }


               svStatAvResponse OBJECT-TYPE
                       SYNTAX INTEGER
                       ACCESS read-only
                       STATUS mandatory
                       ::= { server 14 }


               -- the workstation group


               wkstaStatSessStarts OBJECT-TYPE
                       SYNTAX Counter
                       ACCESS read-only
                       STATUS mandatory
                       ::= { workstation 1 }


               wkstaStatSessFails OBJECT-TYPE
                       SYNTAX Counter
                       ACCESS read-only
                       STATUS mandatory
                       ::= { workstation 2 }


               wkstaStatUses OBJECT-TYPE
                       SYNTAX Counter
                       ACCESS read-only
                       STATUS mandatory
                       ::= { workstation 3 }


               wkstaStatUseFails OBJECT-TYPE
                       SYNTAX Counter
                       ACCESS read-only
                       STATUS mandatory
                       ::= { workstation 4 }








               wkstaStatAutoRecs OBJECT-TYPE
                       SYNTAX Counter
                       ACCESS read-only
                       STATUS mandatory
                       ::= { workstation 5 }


               END
